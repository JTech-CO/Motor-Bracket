# -*- coding: utf-8 -*-
"""FreeCAD 앱 안에서 실행: 형상 직접 읽기 -> 표시 -> 네이티브 저장 -> 재열기 검사.
이 매크로는 외부에서 묶은 FCStd를 읽지 않는다. CAD/BREP 데이터를 직접 읽는다.
실행 결과와 실제 FreeCAD 버전은 native_generated/app_report.json에 기록한다.
현재 배포 환경에서는 FreeCAD GUI 실행 검증을 하지 못했으므로, 실행 결과를 실제 증거로 사용한다.
"""
from pathlib import Path
import json, traceback
import FreeCAD as App
import FreeCADGui as Gui
import Part

_REPORT = None
_OUTPUT = None

def save_report():
    if _REPORT is not None and _OUTPUT is not None:
        (_OUTPUT/'app_report.json').write_text(json.dumps(_REPORT,ensure_ascii=False,indent=2)+'\n',encoding='utf-8')


def root_folder():
    candidate=Path(globals().get('__file__','')).resolve().parent
    if (candidate/'data/import_manifest.json').is_file():return candidate
    try:
        from PySide import QtWidgets as QtGui
    except ImportError:
        from PySide import QtGui
    # __file__이 전달되지 않는 버전은 배포 루트의 parameters.json을 한 번 선택한다.
    selected=QtGui.QFileDialog.getOpenFileName(None,'압축 해제한 폴더의 parameters.json 선택','','JSON (*.json)')
    if isinstance(selected,(tuple,list)):selected=selected[0]
    if not selected:raise RuntimeError('폴더 선택이 취소되었습니다.')
    candidate=Path(selected).parent
    if not (candidate/'data/import_manifest.json').is_file():raise RuntimeError('Rev G 배포 폴더가 아닙니다.')
    return candidate


def run():
    global _REPORT, _OUTPUT
    root=root_folder();out=root/'native_generated';out.mkdir(exist_ok=True)
    _OUTPUT=out
    rows=json.loads((root/'data/import_manifest.json').read_text(encoding='utf-8'))
    report={'FreeCAD_version':list(App.Version()),'executed_inside_FreeCAD':True,'completed':False,'files':[]}
    _REPORT=report;save_report()
    display=None
    for row in rows:
        name=row['name'];shape=Part.Shape()
        try:shape.read(str(root/row['brep']))
        except Exception:shape=Part.Shape()
        if shape.isNull():shape=Part.read(str(root/row['step']))
        if shape.isNull() or not shape.isValid() or len(shape.Solids)!=row['expected_solids'] or shape.Volume<=0:
            raise RuntimeError(name+': 형상 읽기 실패 또는 솔리드 개수 불일치')
        if abs(shape.Volume-row['expected_volume_mm3'])/row['expected_volume_mm3']>1e-5:
            raise RuntimeError(name+': 부피가 예상값과 일치하지 않음')
        doc=App.newDocument('SCMBG_'+name.replace('-','_'));doc.Label=name+' / 한국어 검토본'
        objects=[]
        for i,solid in enumerate(shape.Solids,1):
            obj=doc.addObject('Part::Feature','Solid%02d'%i);obj.Label=row['label']+' / 솔리드 %02d'%i
            obj.Shape=solid;obj.ViewObject.Visibility=True
            obj.ViewObject.ShapeColor=(0.46,0.55,0.64) if i==1 else (0.63,0.67,0.69)
            obj.ViewObject.Transparency=0
            try:obj.ViewObject.DisplayMode='Flat Lines'
            except Exception:pass
            objects.append(obj)
        doc.recompute();Gui.activeDocument().activeView().viewAxonometric();Gui.activeDocument().activeView().fitAll();Gui.updateGui()
        save=out/(name+'.FCStd');doc.saveAs(str(save))
        # FreeCAD 자체 내보내기도 제공한다. 기존 STEP를 텍스트 재포장하지 않는다.
        Part.export(objects,str(out/(name+'.step')))
        App.closeDocument(doc.Name)
        reread=App.openDocument(str(save));App.setActiveDocument(reread.Name)
        solids=[obj for obj in reread.Objects if hasattr(obj,'Shape') and not obj.Shape.isNull()]
        actual=sum(len(obj.Shape.Solids) for obj in solids)
        for obj in solids:obj.ViewObject.Visibility=True;obj.ViewObject.Transparency=0
        if actual!=row['expected_solids']:raise RuntimeError(name+': 네이티브 재열기 검사 실패')
        Gui.activeDocument().activeView().viewAxonometric();Gui.activeDocument().activeView().fitAll();Gui.updateGui()
        reread.recompute();reread.save()
        image_status=False
        try:
            Gui.activeDocument().activeView().saveImage(str(out/(name+'_FreeCAD.png')),1200,900,'White')
            image_status=True
        except Exception:pass
        report['files'].append({'file':name,'solids':actual,'volume_mm3':sum(o.Shape.Volume for o in solids),'all_objects_visible':all(o.ViewObject.Visibility for o in solids),'native_save_and_reopen':True,'viewport_capture_written':image_status})
        save_report()
        if name=='SCMB-G00-PAIR-DEMO':display=reread
        else:App.closeDocument(reread.Name)
    if display:
        App.setActiveDocument(display.Name);Gui.activeDocument().activeView().viewAxonometric();Gui.activeDocument().activeView().fitAll();Gui.updateGui()
    report['completed']=True
    (out/'app_report.json').write_text(json.dumps(report,ensure_ascii=False,indent=2)+'\n',encoding='utf-8')
    App.Console.PrintMessage('\nRev G: 네이티브 저장 및 재열기 검사 완료. native_generated/app_report.json 확인.\n')
    App.Console.PrintMessage('이 결과는 CAD 열기 검사이며, 실물 장착 또는 구조 강도 승인이 아닙니다.\n')

try:run()
except Exception:
    if _REPORT is not None:
        _REPORT['completed']=False;_REPORT['error']=traceback.format_exc();save_report()
    App.Console.PrintError('\nRev G 가져오기 실패. 아래 오류 전체를 기록해 주세요.\n'+traceback.format_exc())
    raise
